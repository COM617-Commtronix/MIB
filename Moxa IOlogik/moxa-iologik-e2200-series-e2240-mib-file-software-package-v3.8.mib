--
-- *****************************************************************
-- Moxa Active Ethernet I/O Server MIB
--
-- 09-17-2009
--
-- Copyright (c) 2008 by Moxa Networking Co., Ltd.
-- All rights reserved.
-- *****************************************************************

MOXA-IO-E2240-MIB DEFINITIONS ::= BEGIN
	IMPORTS
        enterprises, Unsigned32, Integer32, MODULE-IDENTITY, NOTIFICATION-TYPE, OBJECT-TYPE FROM SNMPv2-SMI;

-- 1.3.6.1.4.1.8691.10.2240
--	e2240 OBJECT IDENTIFIER ::= { e2000 2240 }
    e2240   MODULE-IDENTITY
    LAST-UPDATED "201602161500Z"
    ORGANIZATION "Moxa Networking,Inc."
    CONTACT-INFO
            "Postal: Moxa Networking,Inc.
             Fl.4, No.135,Lane 235,Pao-Chiao Rd.
             Shing Tien City,Taipei,Taiwan,R.O.C
             Tel: +866-2-89191230 "

    DESCRIPTION
            "The MIB module for Moxa ioLogik Active Ethernet I/O specific information.(V2.0)" 
            
    REVISION "201602161500Z"    
    DESCRIPTION
            "Update DESCRIPTION sequence for display"  
                  
    REVISION "201601141500Z"
    DESCRIPTION
            "Modify Notification Type.
             Modify doStatus SYNTAX from Unsigned32 to Integer32.
             Modify OBJECT-TYPE Name of doLowWidth to doPulseONWidth. 
             Modify OBJECT-TYPE Name of doHighWidth to doPulseOFFWidth."

    REVISION "200909091716Z"
    DESCRIPTION
            "Updated version of this MIB."
           ::= { e2000 2240 }    -- 1.3.6.1.4.1.8691.10.2240

-- 1.3.6.1.4.1.8691
	moxa OBJECT IDENTIFIER ::= { enterprises 8691 }

-- 1.3.6.1.4.1.8691.10
	e2000 OBJECT IDENTIFIER ::= { moxa 10 }

-- 1.3.6.1.4.1.8691.10.2240.1
	totalChannelNumber OBJECT-TYPE
		SYNTAX Integer32 (1..20)
		MAX-ACCESS read-only
		STATUS current
		DESCRIPTION
			"Total I/O channels."
		::= { e2240 1 }

-- 1.3.6.1.4.1.8691.10.2240.2
	serverModel OBJECT-TYPE
		SYNTAX OCTET STRING
		MAX-ACCESS read-only
		STATUS current
		DESCRIPTION
			"The I/O server model."
		::= { e2240 2 }

-- 1.3.6.1.4.1.8691.10.2240.3
	systemTime OBJECT-TYPE
		SYNTAX Integer32
		MAX-ACCESS read-only
		STATUS current
		DESCRIPTION
			"I/O server up time (in seconds)."
		::= { e2240 3 }

-- 1.3.6.1.4.1.8691.10.2240.4
	firmwareVersion OBJECT-TYPE
		SYNTAX OCTET STRING
		MAX-ACCESS read-only
		STATUS current
		DESCRIPTION
			"The firmware version."
		::= { e2240 4 }

----------------------------------------------------------------
-- I/O
-- 1.3.6.1.4.1.8691.10.2240.10
	e2240monitor OBJECT IDENTIFIER ::= { e2240 10 }

----------------------------------------------------------------
-- ai (Channel 0-8)
aiTable OBJECT-TYPE
		SYNTAX 			SEQUENCE OF AIEntry
		MAX-ACCESS 		not-accessible
		STATUS 			current
		DESCRIPTION		"The ai channel monitor table"
		::= { e2240monitor 1 }

aiEntry OBJECT-TYPE
		SYNTAX			AIEntry
		MAX-ACCESS 		not-accessible
		STATUS 			current
		DESCRIPTION		"The ai channel monitor item"
		INDEX { aiIndex }
		::= { aiTable 1 }

AIEntry ::=	SEQUENCE {
		aiIndex	Integer32,
		aiType		Integer32,
		aiRange	Integer32,
		aiValue	Integer32,
		aiMin		Integer32,
		aiMax		Integer32
}
-------------------------------------------
aiIndex OBJECT-TYPE
		SYNTAX 			Integer32 (1..8)
		MAX-ACCESS 		read-only
		STATUS 			current
		DESCRIPTION		"The ai channel index."
		::= { aiEntry 1 }

aiType OBJECT-TYPE
		SYNTAX 			Integer32 (0)
		MAX-ACCESS 		read-only
		STATUS 			current
		DESCRIPTION		"The ai channel type. AI=0, AO=1"
		::= { aiEntry 2 }
		
aiRange OBJECT-TYPE
		SYNTAX 			Integer32 (0..5)
		MAX-ACCESS 		read-write
		STATUS 			current
		DESCRIPTION		"The ai channel range. +/-150mV=0, +/-500mV=1, +/-5V=2, +/-10V=3, 0-20mA=4, 4-20mA=5"
		::= { aiEntry 3 }
		
aiValue OBJECT-TYPE
		SYNTAX 			Integer32
		MAX-ACCESS 		read-only
		STATUS 			current
		DESCRIPTION		"The ai channel value (RAW)."
		::= { aiEntry 4 }
		
aiMin OBJECT-TYPE
		SYNTAX 			Integer32
		MAX-ACCESS 		read-only
		STATUS 			current
		DESCRIPTION		"The ai channel minimum value (RAW)."
		::= { aiEntry 5 }
		
aiMax OBJECT-TYPE
		SYNTAX 			Integer32
		MAX-ACCESS 		read-only
		STATUS 			current
		DESCRIPTION		"The ai channel maximum value (RAW)."
		::= { aiEntry 6 }


----------------------------------------------------------------
----------------------------------------------------------------
----------------------------------------------------------------
----------------------------------------------------------------
-- ao (channel 0-1)
aoTable OBJECT-TYPE
		SYNTAX 			SEQUENCE OF AOEntry
		MAX-ACCESS 		not-accessible
		STATUS 			current
		DESCRIPTION		"The ao channel-00 monitor table"
		::= { e2240monitor 2 }

aoEntry OBJECT-TYPE
		SYNTAX			AOEntry
		MAX-ACCESS 		not-accessible
		STATUS 			current
		DESCRIPTION		"The ao channel-00 monitor item"
		INDEX { aoIndex }
		::= { aoTable 1 }

AOEntry ::= SEQUENCE {
		aoIndex		Integer32,
		aoType			Integer32,
		aoRange		Integer32,
		aoValue		Integer32
}

aoIndex OBJECT-TYPE
		SYNTAX 			Integer32 (1..2)
		MAX-ACCESS 		read-only
		STATUS 			current
		DESCRIPTION		"The ao channel index."
		::= { aoEntry 1 }

aoType OBJECT-TYPE
		SYNTAX 			Integer32 (1)
		MAX-ACCESS 		read-only
		STATUS 			current
		DESCRIPTION		"The ao channel type. AI=0, AO=1"

		::= { aoEntry 2 }
		
aoRange OBJECT-TYPE
		SYNTAX 			Integer32 (0..1)
		MAX-ACCESS 		read-write
		STATUS 			current
		DESCRIPTION		"The ao channel range. 0~10V=0, 4-20mA=1"
		::= { aoEntry 3 }
		
aoValue OBJECT-TYPE
		SYNTAX 			Integer32
		MAX-ACCESS 		read-write
		STATUS		 	current
		DESCRIPTION		"The ao channel value (RAW)."
		::= { aoEntry 4 }

----------------------------------------------------------------
-- 1.3.6.1.4.1.8691.10.2210.10.4
	logicSettings OBJECT IDENTIFIER ::= { e2240monitor 4 }

----------------------------------------------------------------
irTable OBJECT-TYPE
			SYNTAX 			SEQUENCE OF IrEntry
			MAX-ACCESS 		not-accessible
			STATUS 			current
			DESCRIPTION		"Table of internal registers"
			::= { logicSettings 1 }
                         
irEntry OBJECT-TYPE
		SYNTAX			IrEntry
		MAX-ACCESS 		not-accessible
		STATUS 			current
		DESCRIPTION		"Table of internal registers"
		INDEX { irIndex }
		::= { irTable 1 }

IrEntry ::= SEQUENCE {
		irIndex		    	Integer32,
		irName			OCTET STRING,
		irValue		    	Integer32
}                  

irIndex OBJECT-TYPE
		SYNTAX 			Integer32 (0..23)
		MAX-ACCESS 		read-only
		STATUS 			current
		DESCRIPTION		"The internal register index."
		::= { irEntry 1 }

irName OBJECT-TYPE
		SYNTAX 			OCTET STRING (SIZE (0..19))
		MAX-ACCESS 		read-write
		STATUS 			current
		DESCRIPTION		"The internal register description."
		::= { irEntry 2 }

irValue OBJECT-TYPE
		SYNTAX 			Integer32(0..255)
		MAX-ACCESS 		read-write
		STATUS 			current
		DESCRIPTION		"The internal register working value."
		::= { irEntry 3 }

----------------------------------------------------------------
-- AI TRAP
-- 1.3.6.1.4.1.8691.10.2240.11
-- -------------------------------------------------------------
    aiChannelTrap OBJECT IDENTIFIER 
	::= { e2240 11 }
	
    aiChannel0 OBJECT-TYPE
		SYNTAX	INTEGER {
			none(1),			-- nothing happened
			aiValue(2)			-- aiValue
		}
		MAX-ACCESS	read-only
		STATUS	current
		DESCRIPTION
			"The ai channel-00 value (RAW)."
		::= { aiChannelTrap 1 }	

    aiChannel1 OBJECT-TYPE
		SYNTAX	INTEGER {
			none(1),			-- nothing happened
			aiValue(2)			-- aiValue
		}
		MAX-ACCESS	read-only
		STATUS	current
		DESCRIPTION
			"The ai channel-01 value (RAW)."
		::= { aiChannelTrap 2 }	
		
    aiChannel2 OBJECT-TYPE
		SYNTAX	INTEGER {
			none(1),			-- nothing happened
			aiValue(2)			-- aiValue
		}
		MAX-ACCESS	read-only
		STATUS	current
		DESCRIPTION
			"The ai channel-02 value (RAW)."
		::= { aiChannelTrap 3 }	

    aiChannel3 OBJECT-TYPE
		SYNTAX	INTEGER {
			none(1),			-- nothing happened
			aiValue(2)			-- aiValue
		}
		MAX-ACCESS	read-only
		STATUS	current
		DESCRIPTION
			"The ai channel-03 value (RAW)."
		::= { aiChannelTrap 4 }	

    aiChannel4 OBJECT-TYPE
		SYNTAX	INTEGER {
			none(1),			-- nothing happened
			aiValue(2)			-- aiValue
		}
		MAX-ACCESS	read-only
		STATUS	current
		DESCRIPTION
			"The ai channel-04 value (RAW)."
		::= { aiChannelTrap 5 }	
		
    aiChannel5 OBJECT-TYPE
		SYNTAX	INTEGER {
			none(1),			-- nothing happened
			aiValue(2)			-- aiValue
		}
		MAX-ACCESS	read-only
		STATUS	current
		DESCRIPTION
			"The ai channel-05 value (RAW)."
		::= { aiChannelTrap 6 }	
		
    aiChannel6 OBJECT-TYPE
		SYNTAX	INTEGER {
			none(1),			-- nothing happened
			aiValue(2)			-- aiValue
		}
		MAX-ACCESS	read-only
		STATUS	current
		DESCRIPTION
			"The ai channel-06 value (RAW)."
		::= { aiChannelTrap 7 }	
		
    aiChannel7 OBJECT-TYPE
		SYNTAX	INTEGER {
			none(1),			-- nothing happened
			aiValue(2)			-- aiValue
		}
		MAX-ACCESS	read-only
		STATUS	current
		DESCRIPTION
			"The ai channel-07 value (RAW)."
		::= { aiChannelTrap 8 }													

----------------------------------------------------------------
-- AO TRAP
-- 1.3.6.1.4.1.8691.10.2240.12
-- -------------------------------------------------------------
    aoChannelTrap OBJECT IDENTIFIER 
	::= { e2240 12 }
	
    aoChannel0 OBJECT-TYPE
		SYNTAX	INTEGER {
			none(1),			-- nothing happened
			aoValue(2)			-- aoValue
		}
		MAX-ACCESS	read-only
		STATUS	current
		DESCRIPTION
			"The ao channel-00 value (RAW)."
		::= { aoChannelTrap 1 }	

    aoChannel1 OBJECT-TYPE
		SYNTAX	INTEGER {
			none(1),			-- nothing happened
			aoValue(2)			-- aoValue
		}
		MAX-ACCESS	read-only
		STATUS	current
		DESCRIPTION
			"The ao channel-01 value (RAW)."
		::= { aoChannelTrap 2 }	
		
----------------------------------------------------------------
-- Message TRAP
-- 1.3.6.1.4.1.8691.10.2240.13
----------------------------------------------------------------
	messageTrap OBJECT IDENTIFIER 
	::= { e2240 13 }

    activeMessageTrap OBJECT-TYPE
		SYNTAX	INTEGER {
			none(1),			-- nothing happened
			msgValue(2)			-- message
		}
		MAX-ACCESS	read-only
		STATUS	current
		DESCRIPTION
			"The SNMP trap with active message"
		::= { messageTrap 1 }		
END
