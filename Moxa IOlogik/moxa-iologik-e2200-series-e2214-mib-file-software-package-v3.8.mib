--
-- *****************************************************************
-- Moxa Active Ethernet I/O Server MIB
--
-- 11-04-2009
--
-- Copyright (c) 2005 by Moxa Networking Co., Ltd.
-- All rights reserved.
-- *****************************************************************
--

MOXA-IO-E2214-MIB DEFINITIONS ::= BEGIN
	IMPORTS
        enterprises, Unsigned32, Integer32, MODULE-IDENTITY, NOTIFICATION-TYPE, OBJECT-TYPE FROM SNMPv2-SMI;

-- 1.3.6.1.4.1.8691.10.2214
    e2214   MODULE-IDENTITY
    LAST-UPDATED "201602161500Z"
    ORGANIZATION "Moxa Networking,Inc."
    CONTACT-INFO
            "Postal: Moxa Networking,Inc.
             Fl.4, No.135,Lane 235,Pao-Chiao Rd.
             Shing Tien City,Taipei,Taiwan,R.O.C
             Tel: +866-2-89191230 "

    DESCRIPTION
            "The MIB module for Moxa ioLogik Active Ethernet I/O specific information.(V2.0)" 
            
    REVISION "201602161500Z"    
    DESCRIPTION
            "Update DESCRIPTION sequence for display"  
                  
    REVISION "201601141500Z"
    DESCRIPTION
            "Modify doStatus SYNTAX from Unsigned32 to Integer32.
             Modify OBJECT-TYPE Name of doLowWidth to doPulseONWidth. 
             Modify OBJECT-TYPE Name of doHighWidth to doPulseOFFWidth."
        
    REVISION "201112131900Z"
    DESCRIPTION
            "The MIB module for Moxa ioLogik Active Ethernet I/O specific information." 
            
    REVISION "200911041600Z"
    DESCRIPTION
            "Updated version of this MIB."
           ::= { e2000 2214 }    -- 1.3.6.1.4.1.8691.10.2214

-- 1.3.6.1.4.1.8691
	moxa OBJECT IDENTIFIER ::= { enterprises 8691 }

-- 1.3.6.1.4.1.8691.10
	e2000 OBJECT IDENTIFIER ::= { moxa 10 }

-- 1.3.6.1.4.1.8691.10.2214.1
	totalChannelNumber OBJECT-TYPE
        SYNTAX Integer32 (1..20)
		MAX-ACCESS read-only
		STATUS current
		DESCRIPTION
			"Total I/O channels."
		::= { e2214 1 }

-- 1.3.6.1.4.1.8691.10.2214.2
	serverModel OBJECT-TYPE
		SYNTAX OCTET STRING
		MAX-ACCESS read-only
		STATUS current
		DESCRIPTION
			"The I/O server model."
		::= { e2214 2 }

-- 1.3.6.1.4.1.8691.10.2214.3
	systemTime OBJECT-TYPE
        SYNTAX Integer32
		MAX-ACCESS read-only
		STATUS current
		DESCRIPTION
			"I/O server up time (in seconds)."
		::= { e2214 3 }

-- 1.3.6.1.4.1.8691.10.2214.4
	firmwareVersion OBJECT-TYPE
		SYNTAX OCTET STRING
		MAX-ACCESS read-only
		STATUS current
		DESCRIPTION
			"The firmware version."
		::= { e2214 4 }

----------------------------------------------------------------
-- I/O
-- 1.3.6.1.4.1.8691.10.2214.10
	e2214monitor OBJECT IDENTIFIER ::= { e2214 10 }

----------------------------------------------------------------
-- DI channel
diTable OBJECT-TYPE
        SYNTAX          SEQUENCE OF DiEntry
        MAX-ACCESS      not-accessible
        STATUS          current
        DESCRIPTION     
            "The DI channel monitor table"
		::= {e2214monitor 1 }

diEntry OBJECT-TYPE
        SYNTAX          DiEntry
        MAX-ACCESS      not-accessible
        STATUS          current
        DESCRIPTION     
            "The DI channel monitor item"
		INDEX { diIndex }
		::= { diTable 1 }

DiEntry ::= 
        SEQUENCE {
                diIndex     Integer32,
                diType      Integer32,
                diMode      Integer32,
                diStatus    Unsigned32,
                diFilter    Integer32,
                diTrigger   Integer32,
                diCntStart  Integer32   
                 }

diIndex OBJECT-TYPE
        SYNTAX          Integer32  (0..11)
	MAX-ACCESS 		not-accessible
        STATUS          current
        DESCRIPTION     
            "The channel DI index."
        ::= { diEntry 1 }   

diType OBJECT-TYPE
        SYNTAX          Integer32  (0)
        MAX-ACCESS      read-only
        STATUS          current
        DESCRIPTION     "The channel DI type. 0=DI, 1=DO"
        ::= { diEntry 2 }
		
diMode OBJECT-TYPE
        SYNTAX          Integer32  (0..1)
        MAX-ACCESS      read-write
        STATUS          current
        DESCRIPTION     "The channel DI mode. 0=DI, 1=Event Counter"
        ::= { diEntry 3 }
        
diStatus OBJECT-TYPE
        SYNTAX          Unsigned32 (0..4294967295)
        MAX-ACCESS      read-only
        STATUS          current
        DESCRIPTION     "The channel DI status. 0=Off, 1=On in DI mode or N=Count in counter mode"
        ::= { diEntry 4 }
        
diFilter OBJECT-TYPE
        SYNTAX          Integer32  (1..2000)
        MAX-ACCESS      read-write
        STATUS          current
        DESCRIPTION     "The channel DI counter filter. unit=0.5ms"
        ::= { diEntry 5 }

diTrigger OBJECT-TYPE
        SYNTAX          Integer32  (0..1)
        MAX-ACCESS      read-write
        STATUS          current
        DESCRIPTION     "The channel DI counter trigger level. 0=L2H, 1=H2L"
        ::= { diEntry 6 }

diCntStart OBJECT-TYPE
        SYNTAX          Integer32 (0..1)
        MAX-ACCESS      read-write
        STATUS          current
        DESCRIPTION     "The channel DI counter start/stop. 0=stop, 1=start"
        ::= { diEntry 7 }
----------------------------------------------------------------
-- DO channel
doTable OBJECT-TYPE
        SYNTAX          SEQUENCE OF DOEntry
        MAX-ACCESS      not-accessible
        STATUS          current
   		DESCRIPTION		"The DO channel monitor table"
		::= { e2214monitor 2 }

doEntry OBJECT-TYPE
		SYNTAX			DOEntry
		MAX-ACCESS 		not-accessible
		STATUS 			current
		DESCRIPTION		"The DO channel monitor item"
		INDEX { doIndex }
		::= { doTable 1 }

DOEntry ::= SEQUENCE {
		doIndex		    			Integer32,
		doType			    		Integer32,
		doMode			    		Integer32,
                    doStatus        Integer32,
		doPulseOFFWidth		  Unsigned32,
		doPulseONWidth	    	Unsigned32,
		doPulseStart				Integer32,
		doCurrentRelayCNT  	Integer32,
		doTotalRelayCNT    	Unsigned32
}                       

doIndex OBJECT-TYPE
		SYNTAX 			Integer32 (0..7)
	MAX-ACCESS 		not-accessible
		STATUS 			current
		DESCRIPTION		"The channel DO index."
		::= { doEntry 1 }

doType OBJECT-TYPE
        SYNTAX          Integer32 (0..1)
		MAX-ACCESS 		read-only
		STATUS 			current
		DESCRIPTION		"The channel DO type. 0=DI, DO=1"
		::= { doEntry 2 }
		
doMode OBJECT-TYPE
		SYNTAX 			Integer32 (0..1)
		MAX-ACCESS 		read-write
		STATUS 			current
		DESCRIPTION		"The channel DO mode. 0=DO, 1=Pulse Output"
		::= { doEntry 3 }
		
doStatus OBJECT-TYPE
        SYNTAX          Integer32 (0..1)
		MAX-ACCESS 		read-write
		STATUS 			current
		DESCRIPTION		"The channel DO status. 0=Off, 1=On in DO mode or N=Count in pulse mode"
		::= { doEntry 4 }
		
doPulseOFFWidth OBJECT-TYPE
		SYNTAX 			Unsigned32 (1..65535)
		MAX-ACCESS 		read-write
		STATUS 			current
		DESCRIPTION		"The channel DO signal OFF width. unit=1.5s"
		::= { doEntry 5 }
		
doPulseONWidth OBJECT-TYPE
		SYNTAX 			Unsigned32 (1..65535)
		MAX-ACCESS 		read-write
		STATUS 			current
		DESCRIPTION		"The channel DO signal ON width. unit=1.5s"
		::= { doEntry 6 }
doPulseStart OBJECT-TYPE
		SYNTAX 			Integer32 (0..1)
		MAX-ACCESS 		read-write
		STATUS 			current
		DESCRIPTION		"The channel DO pulse start/stop. 0=stop, 1=start"
		::= { doEntry 7 }
doCurrentRelayCNT OBJECT-TYPE
		SYNTAX 			Integer32 (0..1)
		MAX-ACCESS 		read-write
		STATUS 			current
		DESCRIPTION		"The channel DO relay counter currently."
		::= { doEntry 8}
doTotalRelayCNT OBJECT-TYPE
		SYNTAX 			Unsigned32 (0..4294967295)
		MAX-ACCESS 		read-only
		STATUS 			current
		DESCRIPTION		"The channel DO total relay counter"
		::= { doEntry 9 }		
----------------------------------------------------------------
-- Click&Go
-- 1.3.6.1.4.1.8691.10.2214.10.4
	logicSettings OBJECT IDENTIFIER ::= { e2214monitor 4 }

----------------------------------------------------------------
irTable OBJECT-TYPE
			SYNTAX 			SEQUENCE OF IrEntry
			MAX-ACCESS 		not-accessible
			STATUS 			current
			DESCRIPTION		"Table of internal registers"
			::= { logicSettings 1 }
                         
irEntry OBJECT-TYPE
		SYNTAX			IrEntry
		MAX-ACCESS 		not-accessible
		STATUS 			current
		DESCRIPTION		"Table of internal registers"
		INDEX { irIndex }
		::= { irTable 1 }

IrEntry ::= SEQUENCE {
		irIndex		    Integer32,
		irName			OCTET STRING,
		irValue		    Integer32
}                  

irIndex OBJECT-TYPE
		SYNTAX 			Integer32 (0..23)
		MAX-ACCESS 		read-only
		STATUS 			current
		DESCRIPTION		"The internal register index."
		::= { irEntry 1 }

irName OBJECT-TYPE
		SYNTAX 			OCTET STRING (SIZE (0..19))
		MAX-ACCESS 		read-write
		STATUS 			current
		DESCRIPTION		"The internal register description."
		::= { irEntry 2 }

irValue OBJECT-TYPE
		SYNTAX 			Integer32(0..255)
		MAX-ACCESS 		read-write
		STATUS 			current
		DESCRIPTION		"The internal register working value."
		::= { irEntry 3 }
     
                         
----------------------------------------------------------------
-- DI TRAP
-- 1.3.6.1.4.1.8691.10.2214.11
----------------------------------------------------------------
    diChannelTrap OBJECT IDENTIFIER 
	::= { e2214 11 }

    diChannel0 OBJECT-TYPE
		SYNTAX	INTEGER {
			none(1),			-- nothing happened
			diValue(2)			-- diValue
		}
		MAX-ACCESS	read-only
		STATUS	current
		DESCRIPTION
			"The channel di-00 status. 0=Off, 1=On in DI mode or N=Count in counter mode"
		::= { diChannelTrap 1 }
		
    diChannel1 OBJECT-TYPE
		SYNTAX	INTEGER {
			none(1),			-- nothing happened
			diValue(2)			-- diValue
		}
		MAX-ACCESS	read-only
		STATUS	current
		DESCRIPTION
			"The channel di-01 status. 0=Off, 1=On in DI mode or N=Count in counter mode"
		::= { diChannelTrap 2 }

    diChannel2 OBJECT-TYPE
		SYNTAX	INTEGER {
			none(1),			-- nothing happened
			diValue(2)			-- diValue
		}
		MAX-ACCESS	read-only
		STATUS	current
		DESCRIPTION
			"The channel di-02 status. 0=Off, 1=On in DI mode or N=Count in counter mode"
		::= { diChannelTrap 3 }

    diChannel3 OBJECT-TYPE
		SYNTAX	INTEGER {
			none(1),			-- nothing happened
			diValue(2)			-- diValue
		}
		MAX-ACCESS	read-only
		STATUS	current
		DESCRIPTION
			"The channel di-03 status. 0=Off, 1=On in DI mode or N=Count in counter mode"
		::= { diChannelTrap 4 }

    diChannel4 OBJECT-TYPE
		SYNTAX	INTEGER {
			none(1),			-- nothing happened
			diValue(2)			-- diValue
		}
		MAX-ACCESS	read-only
		STATUS	current
		DESCRIPTION
			"The channel di-04 status. 0=Off, 1=On in DI mode or N=Count in counter mode"
		::= { diChannelTrap 5 }

    diChannel5 OBJECT-TYPE
		SYNTAX	INTEGER {
			none(1),			-- nothing happened
			diValue(2)			-- diValue
		}
		MAX-ACCESS	read-only
		STATUS	current
		DESCRIPTION
			"The channel di-05 status. 0=Off, 1=On in DI mode or N=Count in counter mode"
		::= { diChannelTrap 6 }


----------------------------------------------------------------
-- DO TRAP
-- 1.3.6.1.4.1.8691.10.2214.12
-- -------------------------------------------------------------
    doChannelTrap OBJECT IDENTIFIER 
	::= { e2214 12 }
	
    doChannel0 OBJECT-TYPE
		SYNTAX	INTEGER {
			none(1),			-- nothing happened
			doValue(2)			-- diValue
		}
		MAX-ACCESS	read-only
		STATUS	current
		DESCRIPTION
			"The channel do-00 status. 0=Off, 1=On in DO mode or N=Count in pulse mode"
		::= { doChannelTrap 1 }	

    doChannel1 OBJECT-TYPE
		SYNTAX	INTEGER {
			none(1),			-- nothing happened
			doValue(2)			-- diValue
		}
		MAX-ACCESS	read-only
		STATUS	current
		DESCRIPTION
			"The channel do-01 status. 0=Off, 1=On in DO mode or N=Count in pulse mode"
		::= { doChannelTrap 2 }	

    doChannel2 OBJECT-TYPE
		SYNTAX	INTEGER {
			none(1),			-- nothing happened
			doValue(2)			-- diValue
		}
		MAX-ACCESS	read-only
		STATUS	current
		DESCRIPTION
			"The channel do-02 status. 0=Off, 1=On in DO mode or N=Count in pulse mode"
		::= { doChannelTrap 3 }	

    doChannel3 OBJECT-TYPE
		SYNTAX	INTEGER {
			none(1),			-- nothing happened
			doValue(2)			-- diValue
		}
		MAX-ACCESS	read-only
		STATUS	current
		DESCRIPTION
			"The channel do-03 status. 0=Off, 1=On in DO mode or N=Count in pulse mode"
		::= { doChannelTrap 4 }	

    doChannel4 OBJECT-TYPE
		SYNTAX	INTEGER {
			none(1),			-- nothing happened
			doValue(2)			-- diValue
		}
		MAX-ACCESS	read-only
		STATUS	current
		DESCRIPTION
			"The channel do-04 status. 0=Off, 1=On in DO mode or N=Count in pulse mode"
		::= { doChannelTrap 5 }	

    doChannel5 OBJECT-TYPE
		SYNTAX	INTEGER {
			none(1),			-- nothing happened
			doValue(2)			-- diValue
		}
		MAX-ACCESS	read-only
		STATUS	current
		DESCRIPTION
			"The channel do-05 status. 0=Off, 1=On in DO mode or N=Count in pulse mode"
		::= { doChannelTrap 6 }	

----------------------------------------------------------------
-- current relay counter TRAP
-- 1.3.6.1.4.1.8691.10.2214.13
-- -------------------------------------------------------------
    currentRelayCounterTrap OBJECT IDENTIFIER 
	::= { e2214 13 }
	
    currentRelayCounter0 OBJECT-TYPE
		SYNTAX	INTEGER {
			none(1),			-- nothing happened
			doValue(2)			-- diValue
		}
		MAX-ACCESS	read-only
		STATUS	current
		DESCRIPTION
			"The channel do-00 relay counter currently."
		::= { currentRelayCounterTrap 1 }	

   currentRelayCounter1 OBJECT-TYPE
		SYNTAX	INTEGER {
			none(1),			-- nothing happened
			doValue(2)			-- diValue
		}
		MAX-ACCESS	read-only
		STATUS	current
		DESCRIPTION
			"The channel do-01 relay counter currently.e"
		::= { currentRelayCounterTrap 2 }
		
   currentRelayCounter2 OBJECT-TYPE
		SYNTAX	INTEGER {
			none(1),			-- nothing happened
			doValue(2)			-- diValue
		}
		MAX-ACCESS	read-only
		STATUS	current
		DESCRIPTION
			"The channel do-02 relay counter currently.e"
		::= { currentRelayCounterTrap 3 }
		
   currentRelayCounter3 OBJECT-TYPE
		SYNTAX	INTEGER {
			none(1),			-- nothing happened
			doValue(2)			-- diValue
		}
		MAX-ACCESS	read-only
		STATUS	current
		DESCRIPTION
			"The channel do-03 relay counter currently."
		::= { currentRelayCounterTrap 4 }
		
   currentRelayCounter4 OBJECT-TYPE
		SYNTAX	INTEGER {
			none(1),			-- nothing happened
			doValue(2)			-- diValue
		}
		MAX-ACCESS	read-only
		STATUS	current
		DESCRIPTION
			"The channel do-04 relay counter currently.e"
		::= { currentRelayCounterTrap 5 }
		
   currentRelayCounter5 OBJECT-TYPE
		SYNTAX	INTEGER {
			none(1),			-- nothing happened
			doValue(2)			-- diValue
		}
		MAX-ACCESS	read-only
		STATUS	current
		DESCRIPTION
			"The channel do-05 relay counter currently.e"
		::= { currentRelayCounterTrap 6 }								


----------------------------------------------------------------
-- total relay counter TRAP
-- 1.3.6.1.4.1.8691.10.2214.14
-- -------------------------------------------------------------
    totalRelayCounterTrap OBJECT IDENTIFIER 
	::= { e2214 14 }
	
    totalRelayCounter0 OBJECT-TYPE
		SYNTAX	INTEGER {
			none(1),			-- nothing happened
			doValue(2)			-- diValue
		}
		MAX-ACCESS	read-only
		STATUS	current
		DESCRIPTION
			"The channel do-00 relay counter totally."
		::= { totalRelayCounterTrap 1 }	

   totalRelayCounter1 OBJECT-TYPE
		SYNTAX	INTEGER {
			none(1),			-- nothing happened
			doValue(2)			-- diValue
		}
		MAX-ACCESS	read-only
		STATUS	current
		DESCRIPTION
			"The channel do-01 relay counter totally."
		::= { totalRelayCounterTrap 2 }
		
   totalRelayCounter2 OBJECT-TYPE
		SYNTAX	INTEGER {
			none(1),			-- nothing happened
			doValue(2)			-- diValue
		}
		MAX-ACCESS	read-only
		STATUS	current
		DESCRIPTION
			"The channel do-02 relay counter totally."
		::= { totalRelayCounterTrap 3 }
		
   totalRelayCounter3 OBJECT-TYPE
		SYNTAX	INTEGER {
			none(1),			-- nothing happened
			doValue(2)			-- diValue
		}
		MAX-ACCESS	read-only
		STATUS	current
		DESCRIPTION
			"The channel do-03 relay counter totally."
		::= { totalRelayCounterTrap 4 }
		
   totalRelayCounter4 OBJECT-TYPE
		SYNTAX	INTEGER {
			none(1),			-- nothing happened
			doValue(2)			-- diValue
		}
		MAX-ACCESS	read-only
		STATUS	current
		DESCRIPTION
			"The channel do-04 relay counter totally."
		::= { totalRelayCounterTrap 5 }
		
   totalRelayCounter5 OBJECT-TYPE
		SYNTAX	INTEGER {
			none(1),			-- nothing happened
			doValue(2)			-- diValue
		}
		MAX-ACCESS	read-only
		STATUS	current
		DESCRIPTION
			"The channel do-05 relay counter totally."
		::= { totalRelayCounterTrap 6 }

----------------------------------------------------------------
-- Message TRAP
-- 1.3.6.1.4.1.8691.10.2214.15
----------------------------------------------------------------
	messageTrap OBJECT IDENTIFIER 
	::= { e2214 15 }

    activeMessageTrap OBJECT-TYPE
		SYNTAX	INTEGER {
			none(1),			-- nothing happened
			msgValue(2)			-- message
		}
		MAX-ACCESS	read-only
		STATUS	current
		DESCRIPTION
			"The SNMP trap with active message"
		::= { messageTrap 1 }		
END
