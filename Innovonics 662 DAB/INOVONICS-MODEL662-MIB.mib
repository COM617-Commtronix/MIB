-- INOVONICS MODEL 662 SMIV2 SPECIFICATION MIB

INOVONICS-MODEL662-MIB DEFINITIONS ::= BEGIN

IMPORTS
    MODULE-IDENTITY,OBJECT-TYPE,
    NOTIFICATION-TYPE,enterprises,
    Integer32,IpAddress                     FROM SNMPv2-SMI
    TEXTUAL-CONVENTION,DisplayString        FROM SNMPv2-TC;


model662 MODULE-IDENTITY
    LAST-UPDATED "201705020000Z"
    ORGANIZATION "Inovonics, Inc."
    CONTACT-INFO
                  "www.inovonicsbroadcast.com"
    DESCRIPTION
        "The MIB for the INOmini 662 DAB/DAB+ SiteStreamer."

	REVISION 	"201705020000Z"
	DESCRIPTION
        "First MIB version."
    ::= { inovonicsBroadcast 662 }

inovonicsBroadcast          OBJECT IDENTIFIER ::=  { enterprises 42111 }

traps           			OBJECT IDENTIFIER ::=  { model662 1 }
    notifications           OBJECT IDENTIFIER ::=  { traps 0 }
product                     OBJECT IDENTIFIER ::=  { model662 2 }
nowPlaying                  OBJECT IDENTIFIER ::=  { model662 3 }
    tuner                   OBJECT IDENTIFIER ::=  { nowPlaying 1 }
    radioInfo               OBJECT IDENTIFIER ::=  { nowPlaying 2 }
    ensembleInfo            OBJECT IDENTIFIER ::=  { nowPlaying 3 }
dabInfo                     OBJECT IDENTIFIER ::=  { model662 4 }
alarms                      OBJECT IDENTIFIER ::=  { model662 5 }
setup                       OBJECT IDENTIFIER ::=  { model662 6 }
    network                 OBJECT IDENTIFIER ::=  { setup 1 }
    dynDNS                  OBJECT IDENTIFIER ::=  { setup 2 }
    time                    OBJECT IDENTIFIER ::=  { setup 3 }
    snmp                    OBJECT IDENTIFIER ::=  { setup 4 }
    email                   OBJECT IDENTIFIER ::=  { setup 5 }
    alarmLog                OBJECT IDENTIFIER ::=  { setup 6 }
stationRotation             OBJECT IDENTIFIER ::=  { model662 7 }
passwords                   OBJECT IDENTIFIER ::=  { model662 8 }

-- Custom defined textual-conventions

OnOff ::= TEXTUAL-CONVENTION
    STATUS current
    DESCRIPTION
        "Represents a boolean value."
    SYNTAX INTEGER { off(0), on(1) }

----------------------------------
-- Traps
----------------------------------

audioLossTrap NOTIFICATION-TYPE
    OBJECTS {audioLossAlarm}
	STATUS current
	DESCRIPTION
		"This trap occurs if there is an audio loss alarm."
	::= {notifications 1}

lowSignalTrap NOTIFICATION-TYPE
    OBJECTS {lowSignalAlarm}
	STATUS current
	DESCRIPTION
		"This trap occurs if there is a low signal alarm."
	::= {notifications 2}

dabLossTrap NOTIFICATION-TYPE
    OBJECTS {dabLossAlarm}
	STATUS current
	DESCRIPTION
		"This trap occurs if there is a DAB loss alarm."
	::= {notifications 3}

dlsLossTrap NOTIFICATION-TYPE
    OBJECTS {dlsLossAlarm}
	STATUS current
	DESCRIPTION
		"This trap occurs if there is a DLS loss alarm."
	::= {notifications 4}

----------------------------------
-- Product Info
----------------------------------

version    OBJECT-TYPE
   SYNTAX DisplayString
   MAX-ACCESS read-only
   STATUS current
   DESCRIPTION
      "Current firmware version"
   ::= { product 1 }

date    OBJECT-TYPE
   SYNTAX DisplayString
   MAX-ACCESS read-only
   STATUS current
   DESCRIPTION
      "Date of firmware version"
   ::= { product 2 }

----------------------------------
-- Now Playing
----------------------------------
----------------------------------
-- Now Playing - Tuner
----------------------------------

frequency OBJECT-TYPE
    SYNTAX  Integer32 (174928..239200)
    MAX-ACCESS read-write
    STATUS current
    DESCRIPTION
        "Currently tuned frequency. Can be set
		between 174928 and 239200.
        (Units: kHz, Ex: 174928 == 174.928MHz)."
    ::= { tuner 1 }

tuneServiceID OBJECT-TYPE
    SYNTAX DisplayString (SIZE (1..8))
    MAX-ACCESS read-write
    STATUS current
    DESCRIPTION
        "Currently tuned service ID, in hexadecimal. Can be set
		between 0x00000000 and 0xffffffff."
    ::= { tuner 2 }

tuneComponentID OBJECT-TYPE
    SYNTAX DisplayString (SIZE (1..4))
    MAX-ACCESS read-write
    STATUS current
    DESCRIPTION
        "Currently tuned component ID, in hexadecimal. Can be set
        between 0x0000 and 0xffff."
    ::= { tuner 3 }

currentComponentIndex OBJECT-TYPE
    SYNTAX Integer32 (1..128)
    MAX-ACCESS read-write
    STATUS current
    DESCRIPTION
        "Index of the currently playing component within the
        componentTable."
    ::= { tuner 4 }

currentPreset OBJECT-TYPE
    SYNTAX  Integer32 (1..30)
    MAX-ACCESS read-write
    STATUS current
    DESCRIPTION
        "Currently selected preset. The preset can
		also be set to 1-30. A value of 0 means a
		preset is not selected."
    ::= { tuner 5 }

componentTable OBJECT-TYPE
    SYNTAX SEQUENCE OF ComponentEntry
    MAX-ACCESS not-accessible
    STATUS current
    DESCRIPTION
        "Table of all available components."
    ::= { tuner 6 }

componentEntry OBJECT-TYPE
    SYNTAX ComponentEntry
    MAX-ACCESS not-accessible
    STATUS current
    DESCRIPTION
        "Single component entry."
    INDEX { componentIndex }
    ::= { componentTable 1 }

ComponentEntry ::= SEQUENCE {
    componentIndex Integer32,
    serviceID DisplayString,
    serviceLabel OCTET STRING,
    componentID DisplayString,
    componentLabel OCTET STRING
}

componentIndex OBJECT-TYPE
    SYNTAX Integer32 (1..128)
    MAX-ACCESS not-accessible
    STATUS current
    DESCRIPTION
        "Index of components (component 1 through 128)."
    ::= { componentEntry 1 }

serviceID OBJECT-TYPE
    SYNTAX DisplayString (SIZE (1..8))
    MAX-ACCESS read-only
    STATUS current
    DESCRIPTION
        "The ID of the service holding the component."
    ::= { componentEntry 2 }

serviceLabel OBJECT-TYPE
    SYNTAX OCTET STRING (SIZE (1..16))
    MAX-ACCESS read-only
    STATUS current
    DESCRIPTION
        "The label of the service holding the component."
    ::= { componentEntry 3 }

componentID OBJECT-TYPE
    SYNTAX DisplayString (SIZE (1..4))
    MAX-ACCESS read-only
    STATUS current
    DESCRIPTION
        "Available component ID."
    ::= { componentEntry 4 }

componentLabel OBJECT-TYPE
    SYNTAX OCTET STRING (SIZE (1..16))
    MAX-ACCESS read-only
    STATUS current
    DESCRIPTION
        "Available component label."
    ::= { componentEntry 5 }

----------------------------------
-- Now Playing - Radio Info
----------------------------------

rssi OBJECT-TYPE
    SYNTAX  Integer32
    MAX-ACCESS read-only
    STATUS current
    DESCRIPTION
        "Relative Signal Strength Indicator
		(RF strength). The range is 0-63dBuV."
    ::= { radioInfo 1 }

snr OBJECT-TYPE
    SYNTAX  Integer32
    MAX-ACCESS read-only
    STATUS current
    DESCRIPTION
        "Indicates the current estimate of the digital SNR in dB.
        The range is 0-20dB."
    ::= { radioInfo 2 }

fic OBJECT-TYPE
    SYNTAX  Integer32
    MAX-ACCESS read-only
    STATUS current
    DESCRIPTION
        "Indicates the current estimate of the ensembles FIC quality.
        The range is 0-100."
    ::= { radioInfo 3 }

cnr OBJECT-TYPE
    SYNTAX  Integer32
    MAX-ACCESS read-only
    STATUS current
    DESCRIPTION
        "Indicates the current estimate of the CNR in dB. The CNR
        is the ratio of the OFDM signal level during the on period and
        during the off (null) period. The range is 0-54dB."
    ::= { radioInfo 4 }

fftOffset OBJECT-TYPE
    SYNTAX  Integer32
    MAX-ACCESS read-only
    STATUS current
    DESCRIPTION
        "Indicates the frequency offset of the DQPSK tones of the OFDM signal relative to
        the center of the FFT bins of the digital demod."
    ::= { radioInfo 5 }

fibError OBJECT-TYPE
    SYNTAX  Integer32
    MAX-ACCESS read-only
    STATUS current
    DESCRIPTION
        "Signal-to-Noise Ratio. The range is 0-30dB."
    ::= { radioInfo 6 }

cuLevel OBJECT-TYPE
    SYNTAX  Integer32
    MAX-ACCESS read-only
    STATUS current
    DESCRIPTION
        "Returns the CU usage indicator (number of currently decoded
        CU's). The range is 0-470."
    ::= { radioInfo 7 }

----------------------------------
-- Now Playing - Ensemble Info
----------------------------------

ensembleLabel OBJECT-TYPE
    SYNTAX OCTET STRING (SIZE (1..16))
    MAX-ACCESS read-only
    STATUS current
    DESCRIPTION
        "Ensemble Label."
    ::= { ensembleInfo 1 }

ensembleID OBJECT-TYPE
    SYNTAX DisplayString (SIZE (1..4))
    MAX-ACCESS read-only
    STATUS current
    DESCRIPTION
        "Ensemble ID."
    ::= { ensembleInfo 2 }

totalServices OBJECT-TYPE
    SYNTAX  Integer32
    MAX-ACCESS read-only
    STATUS current
    DESCRIPTION
        "Total services under the ensemble."
    ::= { ensembleInfo 3 }

totalComponents OBJECT-TYPE
    SYNTAX  Integer32
    MAX-ACCESS read-only
    STATUS current
    DESCRIPTION
        "Total components under the ensemble."
    ::= { ensembleInfo 4 }

totalCU OBJECT-TYPE
    SYNTAX  Integer32
    MAX-ACCESS read-only
    STATUS current
    DESCRIPTION
        "Total CU usage under the ensemble."
    ::= { ensembleInfo 5 }

dabTime OBJECT-TYPE
    SYNTAX  DisplayString
    MAX-ACCESS read-only
    STATUS current
    DESCRIPTION
        "Ensemble time adjusted for the local time
        offset or the UTC."
::= { ensembleInfo 6 }

----------------------------------
-- DAB Info
----------------------------------

dls OBJECT-TYPE
    SYNTAX OCTET STRING (SIZE (1..128))
    MAX-ACCESS read-only
    STATUS current
    DESCRIPTION
        "Dynamic Label Segment."
    ::= { dabInfo 1 }

dlsPlus OBJECT-TYPE
    SYNTAX OCTET STRING (SIZE (1..128))
    MAX-ACCESS read-only
    STATUS current
    DESCRIPTION
        "Dynamic Label Plus"
    ::= { dabInfo 2 }

sampleRate OBJECT-TYPE
    SYNTAX  Integer32
    MAX-ACCESS read-only
    STATUS current
    DESCRIPTION
        "Sample rate of the current audio service (Hz)."
    ::= { dabInfo 3 }

bitRate OBJECT-TYPE
    SYNTAX  Integer32
    MAX-ACCESS read-only
    STATUS current
    DESCRIPTION
        "Audio bit rate of the current audio service (kbps)."
    ::= { dabInfo 4 }

dabGain OBJECT-TYPE
    SYNTAX  Integer32 (1..63)
    MAX-ACCESS read-only
    STATUS current
    DESCRIPTION
        "The dynamic range control (DRC) gain that is applied
        to the current audio service. The range of this field is
        from 0 to 63, representing 0 to 15.75dB in increment of 0.25dB."
    ::= { dabInfo 5 }

audioMode OBJECT-TYPE
    SYNTAX INTEGER { dual(0), mono(1), stereo(2), jointStereo(3) }
    MAX-ACCESS read-only
    STATUS current
    DESCRIPTION
        "Audio mode of the current audio service."
    ::= { dabInfo 6 }

serviceMode OBJECT-TYPE
    SYNTAX INTEGER { audioStreamService(0), dataStreamService(1), fidcService(2), mscDataService(3), dabPlus(4), dab(5), ficService(6), xpadData(7), noMedia(8) }
    MAX-ACCESS read-only
    STATUS current
    DESCRIPTION
        "Indicates the service mode of the sub-channel."
    ::= { dabInfo 7 }

protectionInfo OBJECT-TYPE
    SYNTAX INTEGER { none(0), uep1(1), uep2(2), uep3(3) , uep4(4), uep5(5), eep1a(6), eep2a(7), eep3a(8), eep4a(9), eep1b(10), eep2b(11), eep3b(12), eep4b(13)}
    MAX-ACCESS read-only
    STATUS current
    DESCRIPTION
        "Indicates the protection profile of the sub-channel.
        Two error protection profiles can employed: Unequal
        Error Protection (UEP) and Equal Error Protection (EEP)."
    ::= { dabInfo 8 }

cuCurrent OBJECT-TYPE
    SYNTAX  Integer32
    MAX-ACCESS read-only
    STATUS current
    DESCRIPTION
        "The number of Capacity Units assigned to this service component."
    ::= { dabInfo 9 }

cuAddress OBJECT-TYPE
    SYNTAX DisplayString (SIZE (1..4))
    MAX-ACCESS read-only
    STATUS current
    DESCRIPTION
        "The CU starting address of this subchannel within the CIF."
    ::= { dabInfo 10 }

pty OBJECT-TYPE
    SYNTAX  Integer32
    MAX-ACCESS read-only
    STATUS current
    DESCRIPTION
        "Indicates the service program type."
    ::= { dabInfo 11 }

country OBJECT-TYPE
    SYNTAX  DisplayString
    MAX-ACCESS read-only
    STATUS current
    DESCRIPTION
        "Country ID."
    ::= { dabInfo 12 }

globalID OBJECT-TYPE
    SYNTAX  DisplayString
    MAX-ACCESS read-only
    STATUS current
    DESCRIPTION
        "The global reference for the component. The
        SCIdS gets concatenated with the Service ID of
        the service list to form the full global component ID."
    ::= { dabInfo 13 }

language OBJECT-TYPE
    SYNTAX  DisplayString
    MAX-ACCESS read-only
    STATUS current
    DESCRIPTION
        "The language the component is in."
    ::= { dabInfo 14 }

charset OBJECT-TYPE
    SYNTAX  DisplayString
    MAX-ACCESS read-only
    STATUS current
    DESCRIPTION
        "Charset of the ensemble label."
    ::= { dabInfo 15 }

motStatus OBJECT-TYPE
    SYNTAX  DisplayString
    MAX-ACCESS read-only
    STATUS current
    DESCRIPTION
        "Current MOT status."
    ::= { dabInfo 16 }

motProgress OBJECT-TYPE
    SYNTAX  Integer32
    MAX-ACCESS read-only
    STATUS current
    DESCRIPTION
        "Progress of the MOT image acquisition 
        in percent (0 to 100%)."
    ::= { dabInfo 17 }

motName OBJECT-TYPE
    SYNTAX  DisplayString
    MAX-ACCESS read-only
    STATUS current
    DESCRIPTION
        "Filename of the MOT image."
    ::= { dabInfo 18 }

motSize OBJECT-TYPE
    SYNTAX  Integer32
    MAX-ACCESS read-only
    STATUS current
    DESCRIPTION
        "Size of the MOT image in bytes."
    ::= { dabInfo 19 }

----------------------------------
-- Alarms
----------------------------------

audioLossAlarm OBJECT-TYPE
    SYNTAX OnOff
    MAX-ACCESS read-only
    STATUS current
    DESCRIPTION
        "Status of the audio loss alarm"
    ::= { alarms 1 }

lowSignalAlarm OBJECT-TYPE
    SYNTAX OnOff
    MAX-ACCESS read-only
    STATUS current
    DESCRIPTION
        "Status of the low signal alarm"
    ::= { alarms 2 }

dabLossAlarm OBJECT-TYPE
    SYNTAX OnOff
    MAX-ACCESS read-only
    STATUS current
    DESCRIPTION
        "Status of the DAB loss alarm"
    ::= { alarms 3 }

dlsLossAlarm OBJECT-TYPE
    SYNTAX OnOff
    MAX-ACCESS read-only
    STATUS current
    DESCRIPTION
        "Status of the DLS loss alarm"
    ::= { alarms 4 }

audioLossEnable OBJECT-TYPE
    SYNTAX  OnOff
    MAX-ACCESS  read-write
    STATUS  current
    DESCRIPTION
        "Enable the Audio Loss alarm."
    ::= { alarms 5 }

audioLossThreshOn OBJECT-TYPE
    SYNTAX  Integer32 (-40..0)
    MAX-ACCESS  read-write
    STATUS  current
    DESCRIPTION
        "Threshold for alarm turning on (units: dB)."
    ::= { alarms 6 }

audioLossThreshOff OBJECT-TYPE
    SYNTAX  Integer32 (-40..0)
    MAX-ACCESS  read-write
    STATUS  current
    DESCRIPTION
        "Threshold for alarm turning off (units: dB)."
    ::= { alarms 7 }

audioLossTimeOn OBJECT-TYPE
    SYNTAX  Integer32 (5..120)
    MAX-ACCESS  read-write
    STATUS  current
    DESCRIPTION
        "Amount of time the AM level must be below 'threshold on'
        before the alarm turns on (units: seconds)."
    ::= { alarms 8 }

audioLossTimeOff OBJECT-TYPE
    SYNTAX  Integer32 (5..120)
    MAX-ACCESS  read-write
    STATUS  current
    DESCRIPTION
        "Amount of time the AM level must be above 'threshold off'
        before the alarm turns off (units: seconds)."
    ::= { alarms 9 }

lowSignalEnable OBJECT-TYPE
    SYNTAX  OnOff
    MAX-ACCESS  read-write
    STATUS  current
    DESCRIPTION
        "Enable the Low Signal alarm."
    ::= { alarms 10 }

lowSignalThreshOn OBJECT-TYPE
    SYNTAX  Integer32 (0..63)
    MAX-ACCESS  read-write
    STATUS  current
    DESCRIPTION
        "Threshold for alarm turning on (units: dBuV)."
    ::= { alarms 11 }

lowSignalThreshOff OBJECT-TYPE
    SYNTAX  Integer32 (0..63)
    MAX-ACCESS  read-write
    STATUS  current
    DESCRIPTION
        "Threshold for alarm turning off (units: dBuV)."
    ::= { alarms 12 }

lowSignalTimeOn OBJECT-TYPE
    SYNTAX  Integer32 (5..120)
    MAX-ACCESS  read-write
    STATUS  current
    DESCRIPTION
        "Amount of time the RSSI level must be below 'threshold on'
        before the alarm turns on (units: seconds)."
    ::= { alarms 13 }

lowSignalTimeOff OBJECT-TYPE
    SYNTAX  Integer32 (5..120)
    MAX-ACCESS  read-write
    STATUS  current
    DESCRIPTION
        "Amount of time the RSSI level must be above 'threshold off'
        before the alarm turns off (units: seconds)."
    ::= { alarms 14 }

dabLossEnable OBJECT-TYPE
    SYNTAX  OnOff
    MAX-ACCESS  read-write
    STATUS  current
    DESCRIPTION
        "Enable the DAB Loss alarm."
    ::= { alarms 15 }

dabLossTimeOn OBJECT-TYPE
    SYNTAX  Integer32 (5..120)
    MAX-ACCESS  read-write
    STATUS  current
    DESCRIPTION
        "Amount of time the DAB signal must be lost before the alarm turns on (units: seconds)."
    ::= { alarms 16 }

dabLossTimeOff OBJECT-TYPE
    SYNTAX  Integer32 (5..120)
    MAX-ACCESS  read-write
    STATUS  current
    DESCRIPTION
        "Amount of time the DAB signal must be present before the alarm turns off (units: seconds)."
    ::= { alarms 17 }

dlsLossEnable OBJECT-TYPE
    SYNTAX  OnOff
    MAX-ACCESS  read-write
    STATUS  current
    DESCRIPTION
        "Enable the DLS Loss alarm."
    ::= { alarms 18 }

dlsLossTimeOn OBJECT-TYPE
    SYNTAX  Integer32 (5..600)
    MAX-ACCESS  read-write
    STATUS  current
    DESCRIPTION
        "Amount of time passed without a DLS update before the alarm turns on (units: seconds)."
    ::= { alarms 19 }

----------------------------------
-- SETUP
----------------------------------
----------------------------------
-- Setup - Network
----------------------------------

dhcp OBJECT-TYPE
    SYNTAX INTEGER { staticIP(0), dhcpEnabled(1) }
    MAX-ACCESS read-write
    STATUS current
    DESCRIPTION
        "DHCP enabled, or disabled (static IP)."
    ::= { network 1 }

ip OBJECT-TYPE
    SYNTAX IpAddress
    MAX-ACCESS read-write
    STATUS current
    DESCRIPTION
        "Device IP Address."
    ::= { network 2 }

gateway OBJECT-TYPE
    SYNTAX IpAddress
    MAX-ACCESS read-write
    STATUS current
    DESCRIPTION
        "Gateway IP Address."
    ::= { network 3 }

subnet OBJECT-TYPE
    SYNTAX IpAddress
    MAX-ACCESS read-write
    STATUS current
    DESCRIPTION
        "Device subnet mask."
    ::= { network 4 }

dns OBJECT-TYPE
    SYNTAX IpAddress
    MAX-ACCESS read-write
    STATUS current
    DESCRIPTION
        "Device DNS address."
    ::= { network 5 }

httpPort OBJECT-TYPE
    SYNTAX Integer32 (1..65535)
    MAX-ACCESS read-write
    STATUS current
    DESCRIPTION
        "HTTP port for webserver."
    ::= { network 6 }

hostname OBJECT-TYPE
    SYNTAX DisplayString (SIZE (1..15))
    MAX-ACCESS read-write
    STATUS current
    DESCRIPTION
        "NBNS hostname."
    ::= { network 7 }

mac OBJECT-TYPE
    SYNTAX DisplayString
    MAX-ACCESS read-only
    STATUS current
    DESCRIPTION
        "MAC address of this device."
    ::= { network 8 }

----------------------------------
-- Setup - Dynamic DNS
----------------------------------

ddnsMode OBJECT-TYPE
    SYNTAX INTEGER { disabled(0), dyn(1), noip(2), dnsomatic(3) }
    MAX-ACCESS read-write
    STATUS current
    DESCRIPTION
        "Dynamic DNS provider/mode."
    ::= { dynDNS 1 }

ddnsHostname OBJECT-TYPE
    SYNTAX DisplayString (SIZE (1..63))
    MAX-ACCESS read-write
    STATUS current
    DESCRIPTION
        "Your DDNS hostname (proper web addess)."
    ::= { dynDNS 2 }

ddnsUsername OBJECT-TYPE
    SYNTAX DisplayString (SIZE (1..63))
    MAX-ACCESS read-write
    STATUS current
    DESCRIPTION
        "The username for your DDNS account."
    ::= { dynDNS 3 }

ddnsPassword OBJECT-TYPE
    SYNTAX DisplayString (SIZE (1..63))
    MAX-ACCESS read-write
    STATUS current
    DESCRIPTION
        "The password for your DDNS account."
    ::= { dynDNS 4 }

ddnsStatus OBJECT-TYPE
    SYNTAX DisplayString
    MAX-ACCESS read-only
    STATUS current
    DESCRIPTION
        "The status of the DDNS service."
    ::= { dynDNS 5 }

----------------------------------
-- Setup - Time
----------------------------------

timezone OBJECT-TYPE
    SYNTAX Integer32 (-120..140)
    MAX-ACCESS read-write
    STATUS current
    DESCRIPTION
        "UTC offset (units: hours*10). EX: -80 = UTC-8.0.
        Can be set in half hour increments."
    ::= { time 1 }

dst OBJECT-TYPE
    SYNTAX OnOff
    MAX-ACCESS read-write
    STATUS current
    DESCRIPTION
        "Whether Daylight Saving Time is currently in effect."
    ::= { time 2 }

autodst OBJECT-TYPE
    SYNTAX OnOff
    MAX-ACCESS read-write
    STATUS current
    DESCRIPTION
        "Enable to automatically follow US Daylight Saving Time."
    ::= { time 3 }

timeServer OBJECT-TYPE
    SYNTAX DisplayString (SIZE (1..63))
    MAX-ACCESS read-write
    STATUS current
    DESCRIPTION
        "URL for a custom NTP time server."
    ::= { time 4 }

----------------------------------
-- Setup - SNMP
----------------------------------

snmpMode OBJECT-TYPE
    SYNTAX INTEGER { disabled(0), readOnly(1), readWrite(2) }
    MAX-ACCESS read-write
    STATUS current
    DESCRIPTION
        "SNMP mode. Restrict SNMP read or write."
    ::= { snmp 1 }

snmpReadCommunity OBJECT-TYPE
    SYNTAX DisplayString (SIZE (1..31))
    MAX-ACCESS read-write
    STATUS current
    DESCRIPTION
        "SNMP read community string for read access."
    ::= { snmp 2 }

snmpWriteCommunity OBJECT-TYPE
    SYNTAX DisplayString (SIZE (1..31))
    MAX-ACCESS read-write
    STATUS current
    DESCRIPTION
        "SNMP write community string for write access."
    ::= { snmp 3 }

snmpPort OBJECT-TYPE
    SYNTAX Integer32 (1..65535)
    MAX-ACCESS read-write
    STATUS current
    DESCRIPTION
        "UDP port for SNMP communication.
        SNMP standard is UDP port 161."
    ::= { snmp 4 }

snmpTrapsPort OBJECT-TYPE
    SYNTAX Integer32 (1..65535)
    MAX-ACCESS read-write
    STATUS current
    DESCRIPTION
        "UDP port for SNMP traps.
        SNMP standard is UDP port 162."
    ::= { snmp 5 }

snmpTrapDestination1 OBJECT-TYPE
    SYNTAX IpAddress
    MAX-ACCESS read-write
    STATUS current
    DESCRIPTION
        "IP address 1 to send traps to."
    ::= { snmp 6 }

snmpTrapDestination2 OBJECT-TYPE
    SYNTAX IpAddress
    MAX-ACCESS read-write
    STATUS current
    DESCRIPTION
        "IP address 2 to send traps to."
    ::= { snmp 7 }

snmpTrapDestination3 OBJECT-TYPE
    SYNTAX IpAddress
    MAX-ACCESS read-write
    STATUS current
    DESCRIPTION
        "IP address 3 to send traps to."
    ::= { snmp 8 }

----------------------------------
-- Setup - Email
----------------------------------

smtpServer OBJECT-TYPE
    SYNTAX DisplayString (SIZE (1..63))
    MAX-ACCESS read-write
    STATUS current
    DESCRIPTION
        "URL or IP of SMTP server."
    ::= { email 1 }

smtpPort OBJECT-TYPE
    SYNTAX Integer32 (1..65535)
    MAX-ACCESS read-write
    STATUS current
    DESCRIPTION
        "TCP port for SMTP (depends on server)."
    ::= { email 2 }

ssl OBJECT-TYPE
    SYNTAX OnOff
    MAX-ACCESS read-write
    STATUS current
    DESCRIPTION
        "Enable/disable SSL security for connection
        to SMTP server."
    ::= { email 3 }

emailFrom OBJECT-TYPE
    SYNTAX DisplayString (SIZE (1..63))
    MAX-ACCESS read-write
    STATUS current
    DESCRIPTION
        "This will show as the 'From' when you receive
        emails from this unit."
    ::= { email 4 }

emailUsername OBJECT-TYPE
    SYNTAX DisplayString (SIZE (1..63))
    MAX-ACCESS read-write
    STATUS current
    DESCRIPTION
        "The email address to send from."
    ::= { email 5 }

emailPassword OBJECT-TYPE
    SYNTAX DisplayString (SIZE (1..31))
    MAX-ACCESS read-write
    STATUS current
    DESCRIPTION
        "The password to the email address to send from."
    ::= { email 6 }

recipientTable OBJECT-TYPE
    SYNTAX SEQUENCE OF RecipientEntry
    MAX-ACCESS not-accessible
    STATUS current
    DESCRIPTION
        "Table of 10 email recipients."
    ::= { email 7 }

recipientEntry OBJECT-TYPE
    SYNTAX RecipientEntry
    MAX-ACCESS not-accessible
    STATUS current
    DESCRIPTION
        "Single recipient entry."
    INDEX { recipientIndex }
    ::= { recipientTable 1 }

RecipientEntry ::= SEQUENCE {
    recipientIndex Integer32,
    emailAddress DisplayString,
    audioLossEmail OnOff,
    lowSignalEmail OnOff,
    dabLossEmail OnOff,
    dlsLossEmail OnOff,
    dailyLogEmail OnOff,
    weeklyLogEmail OnOff,
    monthlyLogEmail OnOff
}

recipientIndex OBJECT-TYPE
    SYNTAX Integer32 (1..10)
    MAX-ACCESS not-accessible
    STATUS current
    DESCRIPTION
        "Index of recipient (recipients 1 through 10)."
    ::= { recipientEntry 1 }

emailAddress OBJECT-TYPE
    SYNTAX DisplayString (SIZE (1..63))
    MAX-ACCESS read-write
    STATUS current
    DESCRIPTION
        "Email address for the recipient of email notifications."
    ::= { recipientEntry 2 }

audioLossEmail OBJECT-TYPE
    SYNTAX OnOff
    MAX-ACCESS read-write
    STATUS current
    DESCRIPTION
        "This recipient will receive AM Audio Loss emails."
    ::= { recipientEntry 3 }

lowSignalEmail OBJECT-TYPE
    SYNTAX OnOff
    MAX-ACCESS read-write
    STATUS current
    DESCRIPTION
        "This recipient will receive Low Signal emails."
    ::= { recipientEntry 4 }

dabLossEmail OBJECT-TYPE
    SYNTAX OnOff
    MAX-ACCESS read-write
    STATUS current
    DESCRIPTION
        "This recipient will receive DAB Loss emails."
    ::= { recipientEntry 5 }

dlsLossEmail OBJECT-TYPE
    SYNTAX OnOff
    MAX-ACCESS read-write
    STATUS current
    DESCRIPTION
        "This recipient will receive DLS Loss emails."
    ::= { recipientEntry 6 }

dailyLogEmail OBJECT-TYPE
    SYNTAX OnOff
    MAX-ACCESS read-write
    STATUS current
    DESCRIPTION
        "This recipient will receive daily log emails."
    ::= { recipientEntry 7 }

weeklyLogEmail OBJECT-TYPE
    SYNTAX OnOff
    MAX-ACCESS read-write
    STATUS current
    DESCRIPTION
        "This recipient will receive weekly log emails."
    ::= { recipientEntry 8 }

monthlyLogEmail OBJECT-TYPE
    SYNTAX OnOff
    MAX-ACCESS read-write
    STATUS current
    DESCRIPTION
        "This recipient will receive monthly log emails."
    ::= { recipientEntry 9 }

----------------------------------
-- Setup - Alarm Log Settings
----------------------------------

alarmLogStatus OBJECT-TYPE
    SYNTAX Integer32 (0..100)
    MAX-ACCESS read-write
    STATUS current
    DESCRIPTION
        "Fullness of alarm log (units: %). Set to 0 to clear the alarm log."
    ::= { alarmLog 1 }

alarmLogFullEmail OBJECT-TYPE
    SYNTAX Integer32 (1..100)
    MAX-ACCESS read-write
    STATUS current
    DESCRIPTION
        "Send an email reminder when the log is (%) full."
    ::= { alarmLog 2 }

----------------------------------
-- Setup - Miscellaneous
----------------------------------

source OBJECT-TYPE
    SYNTAX  INTEGER{ dabRadio(0), auxInput(1)}
    MAX-ACCESS read-write
    STATUS current
    DESCRIPTION
        "Input source."
    ::= { setup 7 }

gain OBJECT-TYPE
    SYNTAX  INTEGER{ zero(1), minus18(2), minus20(3), minus24(4) }
    MAX-ACCESS read-write
    STATUS current
    DESCRIPTION
        "AUX input gain. This value relative to 0dBFS equals 0VU."
    ::= { setup 8 }

----------------------------------
-- stationRotation
----------------------------------

rotationEnable OBJECT-TYPE
    SYNTAX  OnOff
    MAX-ACCESS  read-write
    STATUS  current
    DESCRIPTION
        "Enable the Station Rotation."
    ::= { stationRotation 1 }

rotationTime OBJECT-TYPE
    SYNTAX  Integer32 (10..300)
    MAX-ACCESS  read-write
    STATUS  current
    DESCRIPTION
        "Amount of time to spend on each station during rotation (Units: seconds)."
    ::= { stationRotation 2 }

----------------------------------
-- Passwords
----------------------------------

webpagesPassword OBJECT-TYPE
    SYNTAX DisplayString (SIZE (1..31))
    MAX-ACCESS read-write
    STATUS current
    DESCRIPTION
        "The password for restricting webpage access."
    ::= { passwords 1 }

END
